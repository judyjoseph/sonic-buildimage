module sonic-kdump {
    namespace "http://github.com/sonic-net/sonic-kdump";
    prefix kdump;
    yang-version 1.1;

    organization
        "SONiC";

    contact
        "SONiC";

    description
        "This module contains a collection of YANG definitions for the
         Linux Kernel crash dumping (Kdump) mechanism. The Kdump feature
         is used to detect and record Linux kernel crash events.";

    revision 2022-05-09 {
        description
            "Initial revision.";
    }

    container sonic-kdump {
        container KDUMP {
            description
                "Kdump configuration parameters";
            container config {
                description "Top level grouping for attributes for Kdump.";
                leaf enabled {
                    type boolean;
                    description
                        "Enable or Disable the Kdump mechanism";
                }

                leaf memory {
                    type string {
                        pattern "((((([0-9]+[MG]?)?(-([0-9]+[MG])?):)?[0-9]+[MG],?)+)|([0-9]+[MG],high))";
                    }
                    description
                        "Memory reserved for loading the crash handler kernel. The amount
                        of reserved memory can be variable, depending on the total amount
                        of installed memory. The syntax for variable memory reservation is
                        <range1>:<size1>,<range2>:<size2>. For example, 512M-2G:64M,2G-:128M,
                        where a memory of 64MB is reserved for the crash kernel for systems
                        with installed memory between 512MB and 2GB, 128MB is reserved for
                        systems that have more than 2GB installed memory. An absolute memory
                        value can also be specified in the format <size>M or <size>G.
                        For example, 512M.";
                }

                leaf num_dumps {
                    type uint8 {
                        range "1 .. 9";
                    }
                    description
                        "Maximum number of Kernel Core files Stored";
                }
                leaf remote {
                    type boolean;
                    description
                        "Enable or Disable the Kdump remote ssh mechanism";
                }

                leaf ssh_string {
                    type string {
                        pattern "([a-zA-Z_][a-zA-Z0-9._%+-]*@([a-zA-Z0-9.-]+|[0-9]{1,3}(\\.[0-9]{1,3}){3}))";
                    }
                    description  "Remote ssh connection string";

                }

                leaf ssh_path {
                    type string {
                        pattern "(/([a-zA-Z0-9._-]+|\\.)+)+";
                    }
                    description  "Remote ssh private key path";

                }

                leaf runtime_arm {
                    type boolean;
                    description
                        "Zero-downtime kdump: reserve crash-kernel memory on the
                        running kernel with no reboot and no crashkernel= boot
                        parameter. Requires a kernel built with the in-tree
                        sonic_kdump_runtime driver (CONFIG_SONIC_KDUMP_RUNTIME=y).";
                }

                leaf runtime_high_memory {
                    type string {
                        pattern "[0-9]+";
                    }
                    description
                        "Size in MB of the high region (may live above 4GB)
                        reserved for the capture kernel when runtime_arm is true.
                        Maps to crashk_res.";
                }

                leaf runtime_low_memory {
                    type string {
                        pattern "[0-9]+";
                    }
                    description
                        "Size in MB of the low (<4GB) region reserved for the
                        capture kernel when runtime_arm is true. Maps to
                        crashk_low_res. Use 0 to skip the low reservation.";
                }

            }
        }
    }
}
